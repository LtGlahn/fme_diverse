FME workspace oppdatervegreferanser_punkt.fmw

Parameters:
- maks_avstand = 200   # Maks avst nærmste veg
- fjern_feilmelding = NEI, ta med duplikater og feil i resultatene
- SourceDataset_XLSXR = $(FME_MF_DIR)Labsys_vegref-20220224.xlsx   # Source Microsoft Excel File(s)
- DestDataset_XLSXW = $(FME_MF_DIR)labsys_vegsystemreferanse_V4.xlsx   # Destination Microsoft Excel File
- DestDataset_OGCGEOPACKAGE = $(FME_MF_DIR)labsys_vegsystemreferanse_V4.gpkg   # GeoPackage File
- SourceDataset_XLSXR_3 = $(FME_MF_DIR)Labsys_vegref-20220224.xlsx   # Source Microsoft Excel File(s)

Readers:
- XLSXR_1: XLSXR from $(SourceDataset_XLSXR)
- XLSXR_2: XLSXR from $(SourceDataset_XLSXR_3)

Writers:
- XLSXW_1: XLSXW to $(DestDataset_XLSXW)
- OGCGEOPACKAGE_1: OGCGEOPACKAGE to $(DestDataset_OGCGEOPACKAGE) in EPSG:5973

Vegref (reader XLSXR_1) [off]
    attributes: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
LABSYS_VEGVESEN.EXPERIS_TEMP_V (reader XLSXR_2)
    attributes: EXPERIS_TEMP_VEGREF_ID number(5,0), PROVE_ID number(6,0), OPPRETTET_DATO datetime, STEDSANGIVELSE_ID number(7,0), UTM_SONE char(1), X_KOORDINAT char(1), Y_KOORDINAT char(1), FYLKE_KODE number(3,0), STATUS_KODE char(2), TYPE_KODE char(2), VEGNR number(4,0), HOVEDPARSELL number(4,0), METER number(6,0), FELTNR number(3,0), AVSTAND_HOYRE_KANT number(5,2), VEGREFERANSE char(20), VEGSYSTEMREFERANSE string, NY_VEGNETTSDATO string, TRAFIKANTGRUPPE string, VEGLENKESEKVENSID char(1), VEGLENKEPOSISJON char(1), VISVEGINFO_X char(1), VISVEGINFO_Y char(1)
    -> Tester_8
Tester_8
    BOOL_OP = OR
    COMPOSITE_TEST = 1
    TEST_CLAUSE = TEST @Value(TYPE_KODE) = G
    TEST_MODE = TEST
    PASSED -> AttributeCopier_2
    FAILED -> AttributeCopier_2
AttributeCopier_2
    ATTR_TABLE:
      COPY FYLKE_KODE > Gammel_Fylkesnummer
      COPY STATUS_KODE > Gammel_Vegkategori
      COPY TYPE_KODE > Gammel_Vegstatus
      COPY VEGNR > Gammel_Vegnummer
      COPY HOVEDPARSELL > Gammel_Fra_HP
      COPY METER > Gammel_Fra_meter
      COPY OPPRETTET_DATO > Gammel_Vegnettdato
      COPY EXPERIS_TEMP_VEGREF_ID > Identitet
      COPY TYPE_KODE > Eks_Vegstatus
    -> Vegref
    -> AttributeCreator_26
Vegref: Inspector
AttributeCreator_26
    ATTR_TABLE = SET_TO FEILMELDING
    -> DuplicateFilter_2
DuplicateFilter_2_Duplicate: Inspector
Sampler_2
    RATE = 100
    SAMPLE_MODE = No
    SAMPLE_TYPE_LONG = First N Features
    SAMPLED -> Tester_10
    NOT_SAMPLED -> Tester_10
Junction_3
    -> AttributeCreator_9
AttributeCreator_9
    ATTR_TABLE = SET_TO FEILMELDING = @Value(FEILMELDING) Visveginfo-stedfesting feiler
    -> Sorter
AttributeCreator_10
    ATTR_TABLE = SET_TO FEILMELDING = @Value(FEILMELDING) Henting av vegsystemreferanse feiler
    -> Sorter
Sorter
    SORT_PARM = EXPERIS_TEMP_VEGREF_ID NUMERIC ASCENDING
    SORTED -> Tester_6
Tester_6
    BOOL_OP = AND
    COMPOSITE_TEST = 1 AND 2
    TEST_CLAUSE:
      TEST startX ATTRIBUTE_HAS_A_VALUE ""
      TEST startY ATTRIBUTE_HAS_A_VALUE ""
    TEST_MODE = TEST
    PASSED -> feiler (writer XLSXW_1)
    PASSED -> VertexCreator
    FAILED -> feiler (writer XLSXW_1)
feiler (writer XLSXW_1)
    attributes: EXPERIS_TEMP_VEGREF_ID number(30), PROVE_ID number(15), FEILMELDING string(60), _fravegref string(200), Ny_Fylkesnummer number(3), Ny_Kommunenummer string(200), Eks_Vegstatus string(200), Gammel_Kommunenummer string(200), _gammeldato datetime(20), FYLKE_KODE number(3), Gammel_Fylkesnummer number(3), STATUS_KODE string(2), Gammel_Vegkategori string(2), TYPE_KODE string(2), Gammel_Vegstatus string(2), VEGNR number(4), Gammel_Vegnummer number(4), HOVEDPARSELL number(4), Gammel_Fra_HP number(4), METER number(6), Gammel_Fra_meter number(6), OPPRETTET_DATO datetime(20), Gammel_Vegnettdato datetime(20), Identitet number(5), STEDSANGIVELSE_ID number(7), UTM_SONE string(1), X_KOORDINAT string(1), Y_KOORDINAT string(1), FELTNR number(3), AVSTAND_HOYRE_KANT number(5),
      VEGREFERANSE string(20), VEGSYSTEMREFERANSE string(20), Ny_Vegnettdato string(20), _response_body string(200), _http_status_code string(20), ReflinkOID string(200), Measure string(200), WKTGeometry string(200), xml_fragment string(200), xml_id string(200), xml_matched_element string(200), xml_parent_id string(200), xml_parent_child_pos string(200), _error string(200), fme_rejection_code string(20), Ny_vegsystemreferanse_fra string(200), geometri string(200), startX number(20), startY number(20), veglenke string(200), Gammel_vegreferanse_FRA string(30), _ViewDate datetime(20)
VertexCreator
    MEASURE_TYPE = Continuous
    MISSING_VAL_MODE = Compute
    MODE_NAME = Add Point
    XVAL = @Value(startX)
    YVAL = @Value(startY)
    -> CoordinateSystemSetter_2
CoordinateSystemSetter_2
    COORDSYS = EPSG:5973
    -> gammalt_vegnett (writer OGCGEOPACKAGE_1)
gammalt_vegnett (writer OGCGEOPACKAGE_1)
    attributes: FEILMELDING text(200), FYLKE_KODE smallint, Gammel_Fylkesnummer smallint, STATUS_KODE text(2), Gammel_Vegkategori text(2), Gammel_Vegstatus text(2), VEGNR smallint, Gammel_Vegnummer smallint, HOVEDPARSELL smallint, Gammel_Fra_HP smallint, METER mediumint, Gammel_Fra_meter mediumint, OPPRETTET_DATO datetime, Gammel_Vegnettdato datetime, EXPERIS_TEMP_VEGREF_ID mediumint, Identitet mediumint, PROVE_ID mediumint, TYPE_KODE text(2), Eks_Vegstatus text(2), STEDSANGIVELSE_ID mediumint, UTM_SONE text(1), X_KOORDINAT text(1), Y_KOORDINAT text(1), FELTNR smallint, AVSTAND_HOYRE_KANT float, VEGREFERANSE text(20), VEGSYSTEMREFERANSE text, NY_VEGNETTSDATO text, TRAFIKANTGRUPPE text, VEGLENKESEKVENSID text(1),
      VEGLENKEPOSISJON text(1), VISVEGINFO_X text(1), VISVEGINFO_Y text(1), Gammel_Kommunenummer text(200), _gammeldato datetime, Ny_Vegnettdato text, startX text(200), startY text(200), veglenke text(200), Gammel_vegreferanse_FRA text(200), _fravegref text(200), _ViewDate datetime, Ny_Fylkesnummer smallint, Ny_Kommunenummer text(200), _response_body text(200), _http_status_code text, ReflinkOID text(200), Measure text(200), WKTGeometry text(200), xml_fragment text(200), xml_id text(200), xml_matched_element text(200), xml_parent_id text(200), xml_parent_child_pos text(200), fme_rejection_code text, Ny_vegsystemreferanse_fra text(200), geometri text(200), _error text(200)
AttributeManager
    ATTR_TABLE:
      RENAME_SET_VALUE startX > visveginfo_X
      RENAME_SET_VALUE startY > visveginfo_Y
      REMOVE FEILMELDING
      SET_TO UTM_SONE = 33
      RENAME_SET_VALUE Ny_vegsystemreferanse_fra > NY_VEGSYSTEMREFERANSE
      RENAME_SET_VALUE Ny_Vegnettdato > NY_VEGNETTSDATO
      REMOVE VEGSYSTEMREFERANSE
      RENAME_SET_VALUE ReflinkOID > VEGLENKESEKVENSID
      RENAME_SET_VALUE Measure > VEGLENKEPOSISJON
      RENAME_SET_VALUE _response_body > VEGLENKEOPPSLAG_JSON
    -> vegsystemreferanse (writer XLSXW_1)
    -> labsys_oppfrisk_vegreferanser (writer OGCGEOPACKAGE_1)
vegsystemreferanse (writer XLSXW_1)
    attributes: EXPERIS_TEMP_VEGREF_ID number(30), PROVE_ID number(10), OPPRETTET_DATO datetime(30), STEDSANGIVELSE_ID number(20), UTM_SONE number(10), X_KOORDINAT number(15), Y_KOORDINAT number(15), Z_KOORDINAT number(15), FYLKE_KODE number(10), STATUS_KODE string(15), TYPE_KODE string(15), VEGNR number(8), HOVEDPARSELL number(15), METER number(10), FELTNR number(10), AVSTAND_HOYRE_KANT number(15), VEGREFERANSE string(25), NY_VEGSYSTEMREFERANSE string(35), NY_VEGNETTSDATO datetime(30), TRAFIKANTGRUPPE string(20), TRAFIKANTGRUPPE_KRYSSYSTEM string(40), TRAFIKANTGRUPPE_SIDEANLEGG string(40), VEGLENKESEKVENSID number(20), VEGLENKEPOSISJON number(20), visveginfo_X number(20), visveginfo_Y number(20), VEGLENKEOPPSLAG_JSON string(500)
labsys_oppfrisk_vegreferanser (writer OGCGEOPACKAGE_1)
    attributes: EXPERIS_TEMP_VEGREF_ID mediumint, PROVE_ID mediumint, NY_VEGSYSTEMREFERANSE text(30), VEGLENKEPOSISJON double, VEGLENKESEKVENSID int, FYLKE_KODE smallint, STATUS_KODE text(2), TYPE_KODE text(2), VEGNR smallint, HOVEDPARSELL smallint, METER mediumint, OPPRETTET_DATO datetime, STEDSANGIVELSE_ID mediumint, UTM_SONE smallint, X_KOORDINAT double, Y_KOORDINAT double, Z_KOORDINAT double, FELTNR smallint, AVSTAND_HOYRE_KANT float, VEGREFERANSE text(20), NY_VEGNETTSDATO datetime, visveginfo_X double, visveginfo_Y double, VEGLENKEOPPSLAG_JSON text, TRAFIKANTGRUPPE text, TRAFIKANTGRUPPE_KRYSSYSTEM text

Bookmark: Duplikatfilter
DuplicateFilter_2
    INPUT_ORDERED_CHOICE = No
    KEYATTR = Identitet
    UNIQUE -> Sampler_2
    DUPLICATE -> AttributeCreator_25
AttributeCreator_25
    ATTR_TABLE = SET_TO FEILMELDING = Duplikat - samme "identitet" kan kun forekomme en gang
    -> Tester_17
Tester_17
    BOOL_OP = OR
    TEST_CLAUSE = CASE_INSENSITIVE_TEST $(fjern_feilmelding) CONTAINS NEI
    TEST_MODE = TEST
    PASSED -> DuplicateFilter_2_Duplicate
    PASSED -> Sampler_2
    FAILED -> DuplicateFilter_2_Duplicate

Bookmark: Inngangsdata
Tester_10
    BOOL_OP = OR
    TEST_CLAUSE:
      TEST @Value(Identitet) = 86
      TEST @Value(Identitet) = 1048
    TEST_MODE = TEST
    PASSED -> Tester_2
    FAILED -> Tester_2
Tester_2
    BOOL_OP = OR
    TEST_CLAUSE = TEST @Value(Identitet) >= 0
    TEST_MODE = TEST
    PASSED -> Tester_7
Tester_7
    BOOL_OP = AND
    TEST_CLAUSE:
      TEST @Value(Gammel_Fylkesnummer) > 0
      TEST Gammel_Vegkategori ATTRIBUTE_HAS_A_VALUE ""
      TEST @Value(Gammel_Vegnummer) > 0
      TEST @Value(Gammel_Fra_HP) > 0
      TEST @Value(Gammel_Fra_meter) >= 0
    TEST_MODE = TEST
    PASSED -> AttributeCreator_3
    FAILED -> AttributeCreator_14
AttributeCreator_14
    ATTR_TABLE = SET_TO FEILMELDING = @Value(FEILMELDING) Ugyldige eller manglende verdier for minst én av: Fylke, kommune, vegkategori, vegstatus, vegnummer, fra HP og/eller frameter
    -> Junction_4
AttributeCreator_3
    ATTR_TABLE = SET_TO _gammeldato = @Value(Gammel_Vegnettdato)
    -> Tester_4
Note: Kommunalveg i Oslo
Tester_4
    BOOL_OP = AND
    COMPOSITE_TEST = 1 AND 2
    TEST_CLAUSE:
      TEST @Value(Gammel_Fylkesnummer) = 3
      TEST @Value(Gammel_Vegkategori) = K
    TEST_MODE = TEST
    PASSED -> AttributeCreator_2
    FAILED -> DateTimeStamper
AttributeCreator_2
    ATTR_TABLE = SET_TO Gammel_Kommunenummer = 1
    -> DateTimeStamper
DateTimeStamper
    DATETIME_ATTR = Ny_Vegnettdato
    STAMP_TYPE = date
    TIMEZONE = local
    -> DateTimeConverter_2
DateTimeConverter_2
    DATETIME_ATTR = _gammeldato
    OUT_FORMAT = %Y-%m-%d
    PASSTHROUGH = NO
    REPAIR_INPUT = YES
    -> NullAttributeMapper
NullAttributeMapper
    ATTRCHOICE = Selected Attributes
    ATTRLIST = Gammel_Kommunenummer
    NEW_VALUE = 0
    NULL_TREATMENT = New Value
    SOURCE_ATTR_VAL = Null Empty "Missing (Selected Attributes Only)"
    -> Tester_5
Note: Kommunalveg uten gyldig kommunenummer?
Tester_5
    BOOL_OP = AND
    COMPOSITE_TEST = 1 AND 2
    TEST_CLAUSE:
      TEST @Value(Gammel_Kommunenummer) = 0
      CASE_INSENSITIVE_TEST @Value(Gammel_Vegkategori) IN K,P,S
    TEST_MODE = PER_TEST
    PASSED -> AttributeCreator_8
    FAILED -> DuplicateFilter
AttributeCreator_8
    ATTR_TABLE = SET_TO FEILMELDING = @Value(FEILMELDING) Kommunenummer kan ikke være 0 på K,P,S - veg
    -> Junction_4
Junction_4
    -> Sorter
DuplicateFilter
    INPUT_ORDERED_CHOICE = No
    KEYATTR = Gammel_Kommunenummer Gammel_Fylkesnummer Gammel_Vegnummer Gammel_Vegstatus Gammel_Fra_HP Gammel_Fra_meter Gammel_Vegnettdato Gammel_Vegkategori
    UNIQUE -> Tester_3
    DUPLICATE -> AttributeCreator_16
AttributeCreator_16
    ATTR_TABLE = SET_TO FEILMELDING = @Value(FEILMELDING)  DUPLIKAT. Oppføring for fylke, vegkategori, vegnummer, hp og meter etc er identisk med tidligere oppføring
    -> Tester_20
Tester_20
    BOOL_OP = OR
    TEST_CLAUSE = CASE_INSENSITIVE_TEST $(fjern_feilmelding) CONTAINS NEI
    TEST_MODE = TEST
    PASSED -> Tester_3
Tester_3
    BOOL_OP = OR
    TEST_CLAUSE:
      CASE_INSENSITIVE_TEST @Value(Gammel_Vegkategori) CONTAINS E
      CASE_INSENSITIVE_TEST @Value(Gammel_Vegkategori) CONTAINS R
      CASE_INSENSITIVE_TEST @Value(Gammel_Vegkategori) CONTAINS F
    TEST_MODE = TEST
    PASSED -> AttributeCreator_5
    FAILED -> Tester
AttributeCreator_5
    ATTR_TABLE = SET_TO Gammel_Kommunenummer = 0
    -> Tester
Tester
    BOOL_OP = OR
    TEST_CLAUSE = TEST Eks_Vegstatus ATTRIBUTE_HAS_A_VALUE ""
    TEST_MODE = TEST
    PASSED -> StringPadder_3
    FAILED -> AttributeCreator

Bookmark: Datamassasje og QA
AttributeCreator
    ATTR_TABLE = SET_TO Eks_Vegstatus = V
    -> StringPadder_3
StringPadder_3
    BLANK_ATTRIBUTE = Yes
    PADCHAR = 0
    SIDE = Left
    SRC_ATTRS = Gammel_Kommunenummer Gammel_Fylkesnummer
    WIDTH = 2
    -> AttributeCreator_18
Note: Fylkes- og kommuenummer endres ikke
AttributeCreator_18
    ATTR_TABLE:
      SET_TO Ny_Fylkesnummer = @Value(Gammel_Fylkesnummer)
      SET_TO Ny_Kommunenummer = @Value(Gammel_Kommunenummer)
    -> StringPadder
StringPadder
    BLANK_ATTRIBUTE = No
    PADCHAR = 0
    SIDE = Left
    SRC_ATTRS = Gammel_Vegnummer Gammel_Fra_meter
    WIDTH = 5
    -> StringPadder_2
StringPadder_2
    BLANK_ATTRIBUTE = No
    PADCHAR = 0
    SIDE = Left
    SRC_ATTRS = Gammel_Fra_HP
    WIDTH = 3
    -> AttributeCreator_6
AttributeCreator_6
    ATTR_TABLE = SET_TO _ViewDate = @Value(Gammel_Vegnettdato)
    -> DateTimeConverter
DateTimeConverter
    DATETIME_ATTR = _ViewDate
    OUT_FORMAT = %Y-%m-%d
    PASSTHROUGH = NO
    REPAIR_INPUT = YES
    -> AttributeCreator_4

Bookmark: Visveginfo FRA
AttributeCreator_4
    ATTR_TABLE = SET_TO _fravegref = @Value(Gammel_Fylkesnummer)@Value(Gammel_Kommunenummer)@Value(Gammel_Vegkategori)@Value(Eks_Vegstatus)@Value(Gammel_Vegnummer)@Value(Gammel_Fra_HP)@Value(Gammel_Fra_meter)
    -> HTTPCaller_2
HTTPCaller_2
    ADDITIONAL_URL_PARAMETERS = roadReference;@Value(_fravegref) topologyLevel;Overview ViewDate;@Value(_ViewDate)
    CONNECTION_TIMEOUT_LENGTH = 60
    ERROR_ATTR = _error
    FOLLOW_REDIRECTS = Yes
    HTTP_METHOD = GET
    SAVE_FILE = Attribute
    STATUS_CODE_ATTR = _http_status_code
    TARGET_ATTR = _response_body
    TARGET_ATTR_ENCODING = auto-detect
    TARGET_URL = http://visveginfo-static.opentns.org/RoadInfoService/GetRoadReferenceForReference
    TRANSFER_TIMEOUT_LENGTH = 90
    USE_COOKIES = No
    VERIFY_SSL_CERTIFICATES = Yes
    -> XMLFragmenter_5
    -> FeatureMerger [REQUESTOR]
    <REJECTED> -> Junction_3
XMLFragmenter_5
    ATTRIBUTE_XML = _response_body
    EMBEDDED_EXPRESSIONS = RoadReference
    FEATURE_TYPES_FORMAT_NAME = XML
    FLATTEN_OPTIONS = <structure separator="." map-empty-elements="yes" matched-prefix="attributes" matched-attributes="yes" cardinality="+{?}" structure-prefix="" child-position-attribute="" except-expression="" ui-mode="basic" matched-ancestor-attributes=""/>
    MERGE_ATTRS = Yes
    NEW_ATTRIBUTES = ReflinkOID Measure WKTGeometry RoadNetPosition.X RoadNetPosition.Y
    XML_SOURCE_TYPE = Attribute with XML document
    FRAGMENTS -> FeatureMerger [SUPPLIER]
    FRAGMENTS -> AttributeCreator_7
FeatureMerger
    ATTR_ACCUM_MODE = Merge Supplier
    ATTR_CONFLICT_RES = Use Requestor
    GEOM_TYPE = Build Aggregates
    IGNORE_NULLS = No
    JOIN_KEYS = @Value(Identitet) @Value(Identitet) AUTO
    MERGE_TYPE = Attributes Only
    PROCESS_DUPS = YES
    REJECT_NULL_MISSING_KEYS = No
    SUPPLIERS_FIRST = No
    UNMERGED_REQUESTOR -> Junction_3
AttributeCreator_7
    ATTR_TABLE:
      SET_TO veglenke = @Value(Measure)@@Value(ReflinkOID)
      SET_TO Gammel_vegreferanse_FRA = @Value(Gammel_Fylkesnummer)@Value(Gammel_Kommunenummer)@Value(Gammel_Vegkategori)@LowerCase(@Value(Gammel_Vegstatus))@int(@Value(Gammel_Vegnummer))hp@int(@Value(Gammel_Fra_HP))m@int(@Value(Gammel_Fra_meter))
    -> AttributeRenamer_5
AttributeRenamer_5
    ATTR_TABLE:
      RENAME_SET_DEFAULT RoadNetPosition.X > startX
      RENAME_SET_DEFAULT RoadNetPosition.Y > startY
    -> HTTPCaller_7

Bookmark: Vegsystemreferanse
HTTPCaller_7
    ADDITIONAL_URL_PARAMETERS = veglenkesekvens;@Value(veglenke)
    CONNECTION_TIMEOUT_LENGTH = 60
    CUSTOM_HEADERS = Accept;application/vnd.vegvesen.nvdb-v3-rev1+json X-Client;FME X-Kontaktperson;jan.kristian.jensen@vegvesen.no
    ERROR_ATTR = _error
    FOLLOW_REDIRECTS = Yes
    HTTP_METHOD = GET
    SAVE_FILE = Attribute
    STATUS_CODE_ATTR = _http_status_code
    TARGET_ATTR = _response_body
    TARGET_ATTR_ENCODING = auto-detect
    TARGET_URL = https://www.vegvesen.no/nvdb/api/v3/veg
    TRANSFER_TIMEOUT_LENGTH = 90
    USE_COOKIES = No
    VERIFY_SSL_CERTIFICATES = Yes
    -> JSONExtractor_3
    <REJECTED> -> Junction_2
JSONExtractor_3
    EXTRACT_QUERY_TABLE = Ny_vegsystemreferanse_fra json["vegsystemreferanse"]["kortform"]
    JSON_DOCUMENT = @Value(_response_body)
    EVALUATED -> JSONExtractor_2
    <REJECTED> -> Junction_2

Bookmark: NVDB api FRA
JSONExtractor_2
    EXTRACT_QUERY_TABLE = geometri json["geometri"]["wkt"]
    JSON_DOCUMENT = @Value(_response_body)
    EVALUATED -> GeometryReplacer
    <REJECTED> -> Junction_2
GeometryReplacer
    KIND_LONG = OGC Well Known Text
    OGC_WKT_PRECISION_DISPLAY = 64-bit
    REMOVE_ATTRIBUTE = Yes
    SOURCE = @Value(geometri)
    -> CoordinateSystemSetter
    <REJECTED> -> Junction_2
Junction_2
    -> AttributeCreator_10
CoordinateSystemSetter
    COORDSYS = EPSG:5973
    -> AttributeRemover
AttributeRemover
    REMOVE_ATTRS = Ny_Fra_HP,Ny_Fra_meter,Ny_Fylkesnummer,Ny_Kommunenummer,Ny_Vegkategori,Ny_Vegnummer,Ny_Vegstatus,Gammel_Fra_HP,Gammel_Fra_meter,Gammel_Fylkesnummer,Gammel_Kommunenummer,Gammel_Vegkategori,Gammel_Vegnettdato,Gammel_Vegnummer,Gammel_vegreferanse_FRA,Gammel_Vegstatus,xml_fragment,xml_id,xml_matched_element,xml_parent_child_pos,xml_parent_id,_fravegref,_gammeldato,_http_status_code,_ViewDate,Eks_Vegstatus,veglenke,WKTGeometry,fme_rejection_code,Identitet,_error
    -> JSONExtractor_4
JSONExtractor_4
    EXTRACT_QUERY_TABLE = TRAFIKANTGRUPPE json["vegsystemreferanse"]["strekning"]["trafikantgruppe"]
    JSON_DOCUMENT = @Value(_response_body)
    EVALUATED -> JSONExtractor_5
JSONExtractor_5
    EXTRACT_QUERY_TABLE = TRAFIKANTGRUPPE_KRYSSYSTEM json["vegsystemreferanse"]["kryssystem"]["trafikantgruppe"]
    JSON_DOCUMENT = @Value(_response_body)
    EVALUATED -> JSONExtractor_6
JSONExtractor_6
    EXTRACT_QUERY_TABLE = TRAFIKANTGRUPPE_SIDEANLEGG json["vegsystemreferanse"]["sideanlegg"]["trafikantgruppe"]
    JSON_DOCUMENT = @Value(_response_body)
    EVALUATED -> CoordinateExtractor
CoordinateExtractor
    IND = 0
    MODE = Specify Coordinate
    X_ATTR = X_KOORDINAT
    Y_ATTR = Y_KOORDINAT
    Z_ATTR = Z_KOORDINAT
    -> AttributeManager
