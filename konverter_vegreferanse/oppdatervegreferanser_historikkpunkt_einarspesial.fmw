FME workspace oppdatervegreferanser_historikkpunkt_einarspesial.fmw

Parameters:
- maks_avstand = 200   # Maks avst nærmste veg
- fjern_feilmelding = NEI, ta med duplikater og feil i resultatene
- DestDataset_OGCGEOPACKAGE = $(FME_MF_DIR)labsys_vegsystemreferanse_V5.gpkg   # GeoPackage File
- SourceDataset_XLSXR_3 = $(FME_MF_DIR)Labsys_vegref-20220224.xlsx   # Source Microsoft Excel File(s)
- DestDataset_XLSXW = $(FME_MF_DIR)labsys_vegsystemreferanse_V5.xlsx   # Destination Microsoft Excel File
- SourceDataset_OGCGEOPACKAGE = C:\DATA\kartverket\Basisdata_0000_Norge_25833_AdministrativeEnheter2017_SOSI\2017admin.gpkg   # GeoPackage File
- SourceDataset_XLSXR = $(FME_MF_DIR)vegreferanser-20220308-med-referansenr fra Einar.xlsx   # Source Microsoft Excel File(s)

Readers:
- XLSXR_1: XLSXR from $(SourceDataset_XLSXR_3)
- OGCGEOPACKAGE_1: OGCGEOPACKAGE from $(SourceDataset_OGCGEOPACKAGE)
- XLSXR_2: XLSXR from $(SourceDataset_XLSXR)

Writers:
- XLSXW_1: XLSXW to $(DestDataset_XLSXW)
- OGCGEOPACKAGE_2: OGCGEOPACKAGE to $(DestDataset_OGCGEOPACKAGE) in EPSG:5973

LABSYS_VEGVESEN.EXPERIS_TEMP_V (reader XLSXR_2)
    attributes: EXPERIS_TEMP_VEGREF_ID number(5,0), PROVE_ID number(6,0), OPPRETTET_DATO datetime, STEDSANGIVELSE_ID number(7,0), UTM_SONE char(1), X_KOORDINAT char(1), Y_KOORDINAT char(1), FYLKE_KODE number(3,0), STATUS_KODE char(2), TYPE_KODE char(2), VEGNR number(4,0), HOVEDPARSELL number(3,0), METER number(6,0), FELTNR number(3,0), AVSTAND_HOYRE_KANT number(5,2), VEGREFERANSE char(19), VEGSYSTEMREFERANSE string, NY_VEGNETTSDATO string, TRAFIKANTGRUPPE string, VEGLENKESEKVENSID char(1), VEGLENKEPOSISJON char(1), VISVEGINFO_X char(1), VISVEGINFO_Y char(1), REFERANSENR number(9,0), VEGREF_KONV char(19)
    -> AttributeKeeper_2
AttributeKeeper_2 [off]
    CREATE_BULK_MODE_FEATURES = NO
    KEEP_ATTRS = AVSTAND_HOYRE_KANT,EXPERIS_TEMP_VEGREF_ID,FELTNR,FYLKE_KODE,HOVEDPARSELL,METER,OPPRETTET_DATO,PROVE_ID,STATUS_KODE,STEDSANGIVELSE_ID,TYPE_KODE,VEGNR,VEGREFERANSE,REFERANSENR,VEGREF_KONV
    -> SubstringExtractor
    -> Tester_10
SubstringExtractor
    END = 1
    RESULT_ATTR = einar_fylkesnr
    SRC_STRING = @Value(VEGREF_KONV)
    START = 0
    -> SubstringExtractor_2
SubstringExtractor_2
    END = 3
    RESULT_ATTR = einar_kommunenr
    SRC_STRING = @Value(VEGREF_KONV)
    START = 2
    -> AttributeCopier
AttributeCopier
    ATTR_TABLE = COPY FYLKE_KODE > fubar_fylkekode
    -> BulkAttributeRenamer
BulkAttributeRenamer
    ATTRCHOICE = All Attributes
    MODE_CHOICE = RENAME
    PATTERN_ACTION_DISP = ADDPREFIX
    REPLACE_STR = labsys_
    -> Sampler_3
Sampler_3
    GROUP_BY = labsys_FYLKE_KODE
    RATE = 1
    SAMPLE_MODE = No
    SAMPLE_TYPE_LONG = First N Features
    SAMPLED -> Baklengs_mapping_fylker [TestFilter_Input]
    NOT_SAMPLED -> Baklengs_mapping_fylker [TestFilter_Input] [off]
Baklengs_mapping_fylker: Baklengs mapping fylker
    FYLKE_KODE = @Value(labsys_FYLKE_KODE)
    Junction_5_Output -> AttributeRenamer
AttributeRenamer
    ATTR_TABLE = RENAME_SET_DEFAULT FYLKE_KODE > vref_FYLKE
    -> AttributeCopier_2
AttributeCopier_2 [off]
    ATTR_TABLE:
      COPY labsys_STATUS_KODE > vref_VEGKAT
      COPY labsys_TYPE_KODE > vref_VEGSTATUS
      COPY labsys_VEGNR > vref_VEGNR
      COPY labsys_HOVEDPARSELL > vref_HP
      COPY labsys_METER > vref_M
      COPY labsys_OPPRETTET_DATO > vref_gammeldato
    -> AttributeCreator_26
AttributeCreator_26
    ATTR_TABLE:
      SET_TO FEILMELDING
      SET_TO vref_KOMMUNE = 0
    -> Junction
Junction
    -> Tester_7
Junction_3
    -> AttributeCreator_9
AttributeCreator_9
    ATTR_TABLE = SET_TO FEILMELDING = @Value(FEILMELDING) Visveginfo-stedfesting feiler
    -> AttributeRemover_2
AttributeCreator_10
    ATTR_TABLE = SET_TO FEILMELDING = @Value(FEILMELDING) Henting av vegsystemreferanse feiler
    -> AttributeRemover_2
AttributeRemover_2
    REMOVE_ATTRS = _http_status_code,_response_body,fme_rejection_code,geometri,Kommunenummer 2022,vegsystemreferanse,vref_gammeldato,vref_HP,vref_M,vref_VEGKAT,vref_VEGNR,vref_VEGSTATUS,WKTGeometry,_error
    -> Tester_6
Tester_6
    BOOL_OP = COMPOSITE
    COMPOSITE_TEST = 1 AND 2
    TEST_CLAUSE:
      TEST visveginfo_X ATTRIBUTE_HAS_A_VALUE ""
      TEST visveginfo_Y ATTRIBUTE_HAS_A_VALUE ""
    TEST_MODE = TEST
    PASSED -> Sorter
    PASSED -> Sorter_3
    FAILED -> Sorter
Sorter
    SORT_PARM = labsys_PROVE_ID NUMERIC ASCENDING labsys_FYLKE_KODE NUMERIC ASCENDING vref_FYLKE NUMERIC ASCENDING
    SORTED -> feiler (writer XLSXW_1)
Note: feiler: labsys_vegsystemreferanse_V5 [XLSXW]
feiler (writer XLSXW_1)
    attributes: labsys_PROVE_ID number(30), FEILMELDING string(50), visveginfo_X number(20), visveginfo_Y number(20), veglenkesekvensid number(20), veglenkeposisjon number(20), veglenke string(30), vegreferanse_oppslag string(30), vref_KOMMUNE number(20), labsys_STATUS_KODE string(20), labsys_TYPE_KODE string(20), labsys_VEGNR number(20), labsys_HOVEDPARSELL number(20), labsys_METER number(20), labsys_OPPRETTET_DATO string(30), vref_FYLKE number(10), labsys_EXPERIS_TEMP_VEGREF_ID number(30), labsys_STEDSANGIVELSE_ID number(30), labsys_FYLKE_KODE number(20), labsys_FELTNR number(20), labsys_AVSTAND_HOYRE_KANT number(30), labsys_VEGREFERANSE string(20), ValidFrom string(10), ValidTo string(10), aar_ValidFrom number(20), aar_ValidTo number(20)
Sorter_3
    SORT_PARM = labsys_PROVE_ID NUMERIC ASCENDING labsys_FYLKE_KODE NUMERIC ASCENDING vref_FYLKE NUMERIC ASCENDING
    SORTED -> VertexCreator
VertexCreator
    MEASURE_TYPE = Continuous
    MISSING_VAL_MODE = Compute
    MODE_NAME = Add Point
    XVAL = @Value(visveginfo_X)
    YVAL = @Value(visveginfo_Y)
    -> CoordinateSystemSetter_2
    <REJECTED> -> VertexCreator__Rejected_
VertexCreator__Rejected_: Inspector
CoordinateSystemSetter_2
    COORDSYS = EPSG:5973
    -> gammalt_vegnett (writer OGCGEOPACKAGE_2)
gammalt_vegnett (writer OGCGEOPACKAGE_2)
    attributes: FEILMELDING text(200), visveginfo_X double, visveginfo_Y double, veglenkesekvensid int, veglenkeposisjon double, veglenke text(30), vegreferanse_oppslag text(30), vref_KOMMUNE int, labsys_STATUS_KODE text(2), labsys_TYPE_KODE text(2), labsys_VEGNR smallint, labsys_HOVEDPARSELL smallint, labsys_METER mediumint, labsys_OPPRETTET_DATO datetime, vref_FYLKE int, labsys_EXPERIS_TEMP_VEGREF_ID mediumint, labsys_PROVE_ID mediumint, labsys_STEDSANGIVELSE_ID mediumint, labsys_FYLKE_KODE smallint, labsys_FELTNR smallint, labsys_AVSTAND_HOYRE_KANT float, labsys_VEGREFERANSE text(20), ValidFrom text(20), ValidTo text(20), aar_ValidFrom float, aar_ValidTo float
Note: Teste gangsti
Tester_8 [off]
    BOOL_OP = OR
    COMPOSITE_TEST = 1
    TEST_CLAUSE = TEST @Value(TYPE_KODE) = G
    TEST_MODE = TEST
Note: Et par testcase
TestFilter_2 [off]
    DEFAULT_VALUE = <UNFILTERED>
    TEST_LIST = "BOOL_OP,OR,COMPOSITE_TEST,""""""1"""""",TEST_CLAUSE,TEST @Value(PROVE_ID) = 5918",5918,"BOOL_OP,OR,COMPOSITE_TEST,""""""1"""""",TEST_CLAUSE,TEST @Value(PROVE_ID) = 170276",170276,"BOOL_OP,OR,COMPOSITE_TEST,""""""1"""""",TEST_CLAUSE,TEST @Value(FYLKE_KODE) = 16",Fylke16,"BOOL_OP,OR,COMPOSITE_TEST,""""""1"""""",TEST_CLAUSE,TEST @Value(FYLKE_KODE) = 17",Fylke17,"BOOL_OP,OR,COMPOSITE_TEST,""""""1"""""",TEST_CLAUSE,TEST @Value(FYLKE_KODE) = 50",Fylke50,"BOOL_OP,OR,COMPOSITE_TEST,""""""1"""""",TEST_CLAUSE,TEST @Value(FYLKE_KODE) <= 20",gamleFylkesnr
Note: Fylker2017
Fylke (reader OGCGEOPACKAGE_1)
    attributes: sosi_eier text(11), sosi_transpar_enhet double, OBJTYPE text(6), sosi_transpar_koordsys_syskode double, FYLKESNAVN_SPRÅK text(4), FYLKESNAVN_REKKEFØLGE double, sosi_objektkatalog_versjon double, sosi_sosi_versjon double, sosi_sosi_nivå double, FYLKESNAVN_NAVN text(17), IDENT_NAVNEROM text(30), sosi_tegnsett text(6), FYLKESNUMMER double, IDENT_LOKALID double, sosi_produsent text(11), SAMISKFORVALTNINGSOMRÅDE text(4), sosi_objektkatalog_kortnavn text(11)
    -> Tester
Tester
    BOOL_OP = OR
    COMPOSITE_TEST = 1
    TEST_CLAUSE = TEST @Value(FYLKESNUMMER) IN 16,17
    TEST_MODE = TEST
    PASSED -> AttributeKeeper
AttributeKeeper
    CREATE_BULK_MODE_FEATURES = NO
    KEEP_ATTRS = FYLKESNUMMER
    -> AttributeRenamer_2
AttributeRenamer_2
    ATTR_TABLE = RENAME_SET_DEFAULT FYLKESNUMMER > sosi_fylkesnummer
    -> PointOnAreaOverlayer [AREA]
PointOnAreaOverlayer
    ATTR_ACCUM_MODE = Merge Incoming
    ATTR_CONFLICT_RES = Use Original
    DEAGGREGATE_INPUT = Yes
    OV_ATTR = _overlaps
    POLYS_FIRST = NO
    POINT -> Tester_3
Tester_3
    BOOL_OP = OR
    COMPOSITE_TEST = 1
    TEST_CLAUSE = TEST @Value(labsys_FYLKE_KODE) = @Value(sosi_fylkesnummer)
    TEST_MODE = TEST
    PASSED -> Sorter_2
    FAILED -> AttributeCreator_3
Sorter_2
    SORT_PARM = labsys_PROVE_ID NUMERIC ASCENDING labsys_FYLKE_KODE NUMERIC ASCENDING vref_FYLKE NUMERIC ASCENDING
    SORTED -> AttributeManager
AttributeManager
    ATTR_TABLE:
      REMOVE FEILMELDING
      REMOVE vref_gammeldato
      RENAME_SET_VALUE _response_body > VEGLENKEOPPSLAG_JSON
    -> labsys_oppfrisk_vegreferanser (writer OGCGEOPACKAGE_2)
    -> vegsystemreferanse (writer XLSXW_1)
Note: vegsystemreferanse: labsys_vegsystemreferanse_V5 [XLSXW]
vegsystemreferanse (writer XLSXW_1)
    attributes: labsys_PROVE_ID number(20), labsys_VEGREFERANSE string(25), vegreferanse_oppslag string(30), labsys_OPPRETTET_DATO string(40), ValidFrom string(25), ValidTo string(25), aar_ValidFrom string(25), aar_ValidTo string(25), vegsystemreferanse string(35), labsys_FYLKE_KODE number(20), vref_FYLKE number(10), vref_KOMMUNE number(20), Kommunenummer 2022 number(25), labsys_STATUS_KODE string(25), vref_VEGKAT string(20), labsys_TYPE_KODE string(25), vref_VEGSTATUS string(15), labsys_VEGNR number(15), vref_VEGNR number(10), labsys_HOVEDPARSELL number(25), vref_HP number(10), labsys_METER number(10), vref_M number(10), labsys_EXPERIS_TEMP_VEGREF_ID number(35), labsys_STEDSANGIVELSE_ID number(30), labsys_FELTNR number(10), labsys_AVSTAND_HOYRE_KANT number(35), TRAFIKANTGRUPPE string(20), TRAFIKANTGRUPPE_KRYSSYSTEM string(30), TRAFIKANTGRUPPE_SIDEANLEGG string(30),
      X_KOORDINAT number(15), Y_KOORDINAT number(15), Z_KOORDINAT number(15), Ny_Vegnettdato string(20), visveginfo_X number(15), visveginfo_Y number(15), veglenkesekvensid number(20), veglenkeposisjon number(20), VEGLENKEOPPSLAG_JSON string(200)
labsys_oppfrisk_vegreferanser (writer OGCGEOPACKAGE_2)
    attributes: visveginfo_X double, visveginfo_Y double, veglenkesekvensid int, veglenkeposisjon float, vegreferanse_oppslag text(30), vref_KOMMUNE int, labsys_STATUS_KODE text(30), vref_VEGKAT text(10), labsys_TYPE_KODE text(20), vref_VEGSTATUS text(20), labsys_VEGNR int, vref_VEGNR int, labsys_HOVEDPARSELL int, vref_HP int, labsys_METER int, vref_M int, labsys_OPPRETTET_DATO datetime, vref_FYLKE int, labsys_EXPERIS_TEMP_VEGREF_ID int, labsys_PROVE_ID int, labsys_STEDSANGIVELSE_ID int, labsys_FYLKE_KODE int, labsys_FELTNR int, labsys_AVSTAND_HOYRE_KANT float, labsys_VEGREFERANSE text(21), VEGLENKEOPPSLAG_JSON text, ValidFrom text(11), ValidTo text(11), aar_ValidFrom float, aar_ValidTo float,
      vegsystemreferanse text(40), Kommunenummer 2022 int, TRAFIKANTGRUPPE text(2), TRAFIKANTGRUPPE_KRYSSYSTEM text(2), TRAFIKANTGRUPPE_SIDEANLEGG text(2), X_KOORDINAT double, Y_KOORDINAT double, Z_KOORDINAT double, Ny_Vegnettdato text
AttributeCreator_3
    ATTR_TABLE = SET_TO FEILMELDING = @Value(FEILMELDING) Filtrerer vekk Feil-Trøndelag pga tvetydighet fylke 16,17 og 50.
    -> Sorter_4
Sorter_4
    SORT_PARM = labsys_PROVE_ID NUMERIC ASCENDING labsys_FYLKE_KODE NUMERIC ASCENDING vref_FYLKE NUMERIC ASCENDING
    SORTED -> avvist_tvetydighet (writer XLSXW_1)
    SORTED -> Feiltrøndelag
    SORTED -> avvist_tvetydighet (writer OGCGEOPACKAGE_2)
Note: avvist_tvetydighet: labsys_vegsystemreferanse_V5 [XLSXW]
avvist_tvetydighet (writer XLSXW_1)
    attributes: labsys_PROVE_ID number(40), FEILMELDING string(50), veglenkesekvensid number(30), veglenkeposisjon number(30), vegsystemreferanse string(30), labsys_VEGREFERANSE string(30), vegreferanse_oppslag string(30), ValidFrom string(20), ValidTo string(20), aar_ValidFrom number(20), aar_ValidTo number(20), vref_KOMMUNE number(20), labsys_STATUS_KODE string(20), vref_VEGKAT string(20), labsys_TYPE_KODE string(20), vref_VEGSTATUS string(20), labsys_VEGNR number(20), vref_VEGNR number(20), labsys_HOVEDPARSELL number(20), vref_HP number(20), labsys_METER number(20), vref_M number(20), labsys_OPPRETTET_DATO string(30), vref_gammeldato datetime(20), vref_FYLKE number(20), sosi_fylkesnummer number(20), labsys_EXPERIS_TEMP_VEGREF_ID number(40), labsys_STEDSANGIVELSE_ID number(30), labsys_FYLKE_KODE number(30), labsys_FELTNR number(30),
      labsys_AVSTAND_HOYRE_KANT number(40), Kommunenummer 2022 number(20), TRAFIKANTGRUPPE string(20), TRAFIKANTGRUPPE_KRYSSYSTEM string(40), TRAFIKANTGRUPPE_SIDEANLEGG string(40), X_KOORDINAT number(20), Y_KOORDINAT number(20), Z_KOORDINAT number(20), Ny_Vegnettdato string(20), visveginfo_X number(25), visveginfo_Y number(25), _response_body string(200)
avvist_tvetydighet (writer OGCGEOPACKAGE_2)
    attributes: FEILMELDING text(200), visveginfo_X text(200), visveginfo_Y text(200), veglenkesekvensid text(200), veglenkeposisjon text(200), vegreferanse_oppslag text(200), vref_KOMMUNE text(200), labsys_STATUS_KODE text(2), vref_VEGKAT text(2), labsys_TYPE_KODE text(2), vref_VEGSTATUS text(2), labsys_VEGNR smallint, vref_VEGNR smallint, labsys_HOVEDPARSELL smallint, vref_HP smallint, labsys_METER mediumint, vref_M mediumint, labsys_OPPRETTET_DATO datetime, vref_gammeldato datetime, vref_FYLKE text(200), labsys_FYLKE_KODE smallint, labsys_fubar_fylkekode smallint, labsys_EXPERIS_TEMP_VEGREF_ID mediumint, labsys_PROVE_ID mediumint, labsys_STEDSANGIVELSE_ID mediumint, labsys_FELTNR smallint, labsys_AVSTAND_HOYRE_KANT float, labsys_VEGREFERANSE text(19), labsys_REFERANSENR mediumint, labsys_VEGREF_KONV text(19),
      labsys_einar_fylkesnr text, labsys_einar_kommunenr text, _response_body text(200), ValidFrom text(200), ValidTo text(200), aar_ValidFrom text(200), aar_ValidTo text(200), vegsystemreferanse text(200), Kommunenummer 2022 text(200), TRAFIKANTGRUPPE text(200), TRAFIKANTGRUPPE_KRYSSYSTEM text(200), TRAFIKANTGRUPPE_SIDEANLEGG text(200), X_KOORDINAT text(200), Y_KOORDINAT text(200), Z_KOORDINAT text(200), Ny_Vegnettdato text, sosi_fylkesnummer double, _overlaps text(200)
Feiltrøndelag: Inspector

Bookmark: Inngangsdata
Tester_7
    BOOL_OP = COMPOSITE
    COMPOSITE_TEST = 1 AND 2 AND 3 AND 4 AND 5 AND 6
    TEST_CLAUSE:
      TEST @Value(vref_FYLKE) > 0
      TEST @Value(vref_VEGKAT) IN E,R,F,K,P,S
      TEST vref_VEGSTATUS ATTRIBUTE_HAS_A_VALUE ""
      TEST @Value(labsys_VEGNR) > 0
      TEST @Value(labsys_HOVEDPARSELL) > 0
      TEST @Value(labsys_METER) >= 0
    TEST_MODE = TEST
    PASSED -> Tester_4
    FAILED -> AttributeCreator_14
AttributeCreator_14
    ATTR_TABLE = SET_TO FEILMELDING = @Value(FEILMELDING) Ugyldige eller manglende verdier for minst én av: Fylke, kommune, vegkategori, vegstatus, vegnummer, fra HP og/eller frameter
    -> Junction_4
Note: Kommunalveg i Oslo
Tester_4
    BOOL_OP = COMPOSITE
    COMPOSITE_TEST = 1 AND 2
    TEST_CLAUSE:
      CASE_INSENSITIVE_TEST @Value(vref_FYLKE) = 3
      CASE_INSENSITIVE_TEST @Value(vref_VEGKAT) IN K,P,S
    TEST_MODE = CASE_INSENSITIVE_TEST
    PASSED -> AttributeCreator_2
    FAILED -> NullAttributeMapper
AttributeCreator_2
    ATTR_TABLE = SET_TO vref_KOMMUNE = 1
    -> DuplicateFilter_2
    -> NullAttributeMapper
DuplicateFilter_2
    INPUT_ORDERED_CHOICE = No
    KEYATTR = vref_VEGKAT
    UNIQUE -> DuplicateFilter_2_Unique
DuplicateFilter_2_Unique: Inspector
NullAttributeMapper
    ATTRCHOICE = Selected Attributes
    ATTRLIST = vref_KOMMUNE
    NEW_VALUE = 0
    NULL_TREATMENT = New Value
    SOURCE_ATTR_VAL = Null Empty "Missing (Selected Attributes Only)"
    -> Tester_5
Note: Kommunalveg uten gyldig kommunenummer?
Tester_5
    BOOL_OP = COMPOSITE
    COMPOSITE_TEST = 1 AND 2
    TEST_CLAUSE:
      TEST @Value(vref_KOMMUNE) = 0
      CASE_INSENSITIVE_TEST @Value(vref_VEGKAT) IN K,P,S
    TEST_MODE = PER_TEST
    PASSED -> AttributeCreator_8
    FAILED -> StringPadder_3
AttributeCreator_8
    ATTR_TABLE = SET_TO FEILMELDING = @Value(FEILMELDING) Kommunenummer kan ikke være 0 på K,P,S - veg
    -> Junction_4
Junction_4
    -> AttributeRemover_2

Bookmark: Datamassasje og QA
StringPadder_3
    BLANK_ATTRIBUTE = Yes
    PADCHAR = 0
    SIDE = Left
    SRC_ATTRS = vref_FYLKE vref_KOMMUNE
    WIDTH = 2
    -> StringPadder
StringPadder
    BLANK_ATTRIBUTE = No
    PADCHAR = 0
    SIDE = Left
    SRC_ATTRS = vref_M vref_VEGNR
    WIDTH = 5
    -> StringPadder_2
StringPadder_2
    BLANK_ATTRIBUTE = No
    PADCHAR = 0
    SIDE = Left
    SRC_ATTRS = vref_HP
    WIDTH = 3
    -> AttributeCreator_4

Bookmark: Visveginfo FRA
AttributeCreator_4
    ATTR_TABLE = SET_TO vegreferanse_oppslag = @Value(vref_FYLKE)@Value(vref_KOMMUNE)@Value(vref_VEGKAT)@Value(vref_VEGSTATUS)@Value(vref_VEGNR)@Value(vref_HP)@Value(vref_M)
    -> HTTPCaller_2
HTTPCaller_2
    ADDITIONAL_URL_PARAMETERS = roadReference;@Value(vegreferanse_oppslag)
    CONNECTION_TIMEOUT_LENGTH = 60
    ERROR_ATTR = _error
    FOLLOW_REDIRECTS = Yes
    HTTP_METHOD = GET
    SAVE_FILE = Attribute
    STATUS_CODE_ATTR = _http_status_code
    TARGET_ATTR = _response_body
    TARGET_ATTR_ENCODING = auto-detect
    TARGET_URL = https://visveginfo.opentns.org/RoadInfoService/GetRoadReferenceHistoryForReference
    TRANSFER_TIMEOUT_LENGTH = 90
    USE_COOKIES = No
    VERIFY_SSL_CERTIFICATES = Yes
    -> XMLFragmenter_5
    -> FeatureMerger [REQUESTOR]
    <REJECTED> -> Junction_3
XMLFragmenter_5
    ATTRIBUTE_XML = _response_body
    EMBEDDED_EXPRESSIONS = RoadPointReferenceWithTimePeriod
    FEATURE_TYPES_FORMAT_NAME = XML
    FLATTEN_OPTIONS = <structure separator="." map-empty-elements="yes" matched-prefix="attributes" matched-attributes="yes" cardinality="+{?}" structure-prefix="" child-position-attribute="" except-expression="" ui-mode="basic" matched-ancestor-attributes=""/>
    MERGE_ATTRS = Yes
    NEW_ATTRIBUTES = ReflinkOID Measure WKTGeometry RoadNetPosition.X RoadNetPosition.Y ValidFrom ValidTo
    XML_SOURCE_TYPE = Attribute with XML document
    FRAGMENTS -> AttributeCreator_7
AttributeCreator_7
    ATTR_TABLE = SET_TO veglenke = @Value(Measure)@@Value(ReflinkOID)
    -> DateTimeConverter_3
DateTimeConverter_3
    DATETIME_ATTR = ValidFrom ValidTo vref_gammeldato
    OUT_FORMAT = FME
    PASSTHROUGH = NO
    REPAIR_INPUT = YES
    -> ExpressionEvaluator_2
ExpressionEvaluator_2
    ACTION = Create New Attribute
    EXPRESSION = @DateTimeDiff( @Value(vref_gammeldato), @Value(ValidFrom), Years )
    VAL_ATTR = aar_ValidFrom
    -> ExpressionEvaluator
ExpressionEvaluator
    ACTION = Create New Attribute
    EXPRESSION = @DateTimeDiff( @Value(vref_gammeldato), @Value(ValidTo), Years )
    VAL_ATTR = aar_ValidTo
    -> DateTimeConverter_4
DateTimeConverter_4
    DATETIME_ATTR = ValidFrom ValidTo vref_gammeldato
    OUT_FORMAT = %Y-%m-%d
    PASSTHROUGH = NO
    REPAIR_INPUT = YES
    -> AttributeRenamer_5
AttributeRenamer_5
    ATTR_TABLE:
      RENAME_SET_DEFAULT RoadNetPosition.X > visveginfo_X
      RENAME_SET_DEFAULT RoadNetPosition.Y > visveginfo_Y
      RENAME_SET_DEFAULT ReflinkOID > veglenkesekvensid
      RENAME_SET_DEFAULT Measure > veglenkeposisjon
    -> BulkAttributeRemover
    -> FeatureMerger [SUPPLIER]
FeatureMerger
    ATTR_ACCUM_MODE = Merge Supplier
    ATTR_CONFLICT_RES = Use Requestor
    GEOM_TYPE = Build Aggregates
    IGNORE_NULLS = No
    JOIN_KEYS = @Value(labsys_PROVE_ID) @Value(labsys_PROVE_ID) AUTO
    MERGE_TYPE = Attributes Only
    PROCESS_DUPS = YES
    REJECT_NULL_MISSING_KEYS = No
    SUPPLIERS_FIRST = No
    UNMERGED_REQUESTOR -> Junction_3
BulkAttributeRemover
    ATTR_EXP = xml_
    -> HTTPCaller_7

Bookmark: Vegsystemreferanse
HTTPCaller_7
    ADDITIONAL_URL_PARAMETERS = veglenkesekvens;@Value(veglenke)
    CONNECTION_TIMEOUT_LENGTH = 60
    CUSTOM_HEADERS = Accept;application/vnd.vegvesen.nvdb-v3-rev1+json X-Client;FME X-Kontaktperson;jan.kristian.jensen@vegvesen.no
    ERROR_ATTR = _error
    FOLLOW_REDIRECTS = Yes
    HTTP_METHOD = GET
    SAVE_FILE = Attribute
    STATUS_CODE_ATTR = _http_status_code
    TARGET_ATTR = _response_body
    TARGET_ATTR_ENCODING = auto-detect
    TARGET_URL = https://www.vegvesen.no/nvdb/api/v3/veg
    TRANSFER_TIMEOUT_LENGTH = 90
    USE_COOKIES = No
    VERIFY_SSL_CERTIFICATES = Yes
    -> JSONExtractor_3
    <REJECTED> -> Junction_2
JSONExtractor_3
    EXTRACT_QUERY_TABLE = vegsystemreferanse json["vegsystemreferanse"]["kortform"]
    JSON_DOCUMENT = @Value(_response_body)
    EVALUATED -> JSONExtractor_7
    <REJECTED> -> Junction_2
JSONExtractor_7
    EXTRACT_QUERY_TABLE = "Kommunenummer 2022" json["kommune"]
    JSON_DOCUMENT = @Value(_response_body)
    EVALUATED -> JSONExtractor_2
    <REJECTED> -> Junction_2
JSONExtractor_2
    EXTRACT_QUERY_TABLE = geometri json["geometri"]["wkt"]
    JSON_DOCUMENT = @Value(_response_body)
    EVALUATED -> GeometryReplacer
    <REJECTED> -> Junction_2

Bookmark: NVDB api FRA
GeometryReplacer
    KIND_LONG = OGC Well Known Text
    OGC_WKT_PRECISION_DISPLAY = 64-bit
    REMOVE_ATTRIBUTE = Yes
    SOURCE = @Value(geometri)
    -> CoordinateSystemSetter
    <REJECTED> -> Junction_2
Junction_2
    -> AttributeCreator_10
CoordinateSystemSetter
    COORDSYS = EPSG:5973
    -> JSONExtractor_4
JSONExtractor_4
    EXTRACT_QUERY_TABLE = TRAFIKANTGRUPPE json["vegsystemreferanse"]["strekning"]["trafikantgruppe"]
    JSON_DOCUMENT = @Value(_response_body)
    EVALUATED -> JSONExtractor_5
JSONExtractor_5
    EXTRACT_QUERY_TABLE = TRAFIKANTGRUPPE_KRYSSYSTEM json["vegsystemreferanse"]["kryssystem"]["trafikantgruppe"]
    JSON_DOCUMENT = @Value(_response_body)
    EVALUATED -> JSONExtractor_6
JSONExtractor_6
    EXTRACT_QUERY_TABLE = TRAFIKANTGRUPPE_SIDEANLEGG json["vegsystemreferanse"]["sideanlegg"]["trafikantgruppe"]
    JSON_DOCUMENT = @Value(_response_body)
    EVALUATED -> CoordinateExtractor
CoordinateExtractor
    IND = 0
    MODE = Specify Coordinate
    X_ATTR = X_KOORDINAT
    Y_ATTR = Y_KOORDINAT
    Z_ATTR = Z_KOORDINAT
    -> AttributeRemover
AttributeRemover
    REMOVE_ATTRS = _http_status_code,veglenke,WKTGeometry
    -> DateTimeStamper
DateTimeStamper
    DATETIME_ATTR = Ny_Vegnettdato
    STAMP_TYPE = date
    TIMEZONE = local
    -> Tester_2
Tester_2
    BOOL_OP = OR
    COMPOSITE_TEST = 1
    TEST_CLAUSE = TEST @Value(labsys_FYLKE_KODE) IN 16,17
    TEST_MODE = TEST
    PASSED -> PointOnAreaOverlayer [POINT]
    FAILED -> Sorter_2

Bookmark: statistikk
Tester_10 [off]
    BOOL_OP = OR
    COMPOSITE_TEST = 1
    TEST_CLAUSE = TEST @Value(FYLKE_KODE) IN 16,17,50
    TEST_MODE = TEST
    PASSED -> AttributeCreator [off]
AttributeCreator [off]
    ATTR_TABLE = SET_TO regionreform = 2018-01-01
    -> DateTimeConverter_2 [off]
DateTimeConverter_2 [off]
    DATETIME_ATTR = OPPRETTET_DATO regionreform
    OUT_FORMAT = FME
    PASSTHROUGH = NO
    REPAIR_INPUT = YES
    -> ExpressionEvaluator_3 [off]
ExpressionEvaluator_3 [off]
    ACTION = Create New Attribute
    EXPRESSION = @DateTimeDiff( @Value(regionreform), @Value(OPPRETTET_DATO), Years )
    VAL_ATTR = aar_ValidFrom
    -> Tester_9 [off]
Tester_9 [off]
    BOOL_OP = OR
    COMPOSITE_TEST = 1
    TEST_CLAUSE = NUM_TEST @Value(aar_ValidFrom) < 0
    TEST_MODE = NUM_TEST
    PASSED -> StatisticsCalculator [off]
    FAILED -> StatisticsCalculator_2 [off]
StatisticsCalculator [off]
    CALCULATION_MODE = NUMERIC
    FEAT_STATS = FYLKE_KODE,NUMERIC_MODE,,,COUNT,,,,,,,,,
    GROUP_BY = FYLKE_KODE
    SUMMARY -> PRE_regionreform [off]
PRE_regionreform: Inspector [off]
StatisticsCalculator_2 [off]
    CALCULATION_MODE = NUMERIC
    FEAT_STATS = FYLKE_KODE,NUMERIC_MODE,,,COUNT,,,,,,,,,
    GROUP_BY = FYLKE_KODE
    SUMMARY -> POST_regionreform [off]
POST_regionreform: Inspector [off]
LABSYS_VEGVESEN.EXPERIS_TEMP_V (reader XLSXR_1) [off]
    attributes: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
DuplicateFilter_3 [off]
    INPUT_ORDERED_CHOICE = No
    KEYATTR = FYLKE_KODE
    UNIQUE -> DuplicateFilter_3_Unique [off]
DuplicateFilter_3_Unique: Inspector [off]

FME custom transformer Baklengs mapping fylker

Parameters:
- FYLKE_KODE = @Value(FYLKE_KODE)   # Fylke Kode

TestFilter_Input (input)
    -> TestFilter
TestFilter
    DEFAULT_VALUE = <UNFILTERED>
    TEST_LIST = "BOOL_OP,OR,COMPOSITE_TEST,""""""1"""""",TEST_CLAUSE,TEST @Value(FYLKE_KODE) = 16",Fylke16,"BOOL_OP,OR,COMPOSITE_TEST,""""""1"""""",TEST_CLAUSE,TEST @Value(FYLKE_KODE) = 17",Fylke17,"BOOL_OP,OR,COMPOSITE_TEST,""""""1"""""",TEST_CLAUSE,TEST @Value(FYLKE_KODE) = 50",Fylke50,"BOOL_OP,OR,COMPOSITE_TEST,""""""1"""""",TEST_CLAUSE,TEST @Value(FYLKE_KODE) <= 20",gamleFylkesnr,"BOOL_OP,OR,COMPOSITE_TEST,""""""1"""""",TEST_CLAUSE,TEST @Value(FYLKE_KODE) = 51",Fylke51,"BOOL_OP,OR,COMPOSITE_TEST,""""""1"""""",TEST_CLAUSE,TEST @Value(FYLKE_KODE) = 52",Fylke52,"BOOL_OP,OR,COMPOSITE_TEST,""""""1"""""",TEST_CLAUSE,TEST @Value(FYLKE_KODE) = 52",Fylke52,"BOOL_OP,OR,COMPOSITE_TEST,""""""1"""""",TEST_CLAUSE,TEST @Value(FYLKE_KODE) = 53",Fylke53,"BOOL_OP,OR,COMPOSITE_TEST,""""""1"""""",TEST_CLAUSE,TEST @Value(FYLKE_KODE) = 54",Fylke54,"BOOL_OP,OR,COMPOSITE_TEST,""""""1"""""",TEST_CLAUSE,TEST @Value(FYLKE_KODE) = 55",Fylke55,"BOOL_OP,OR,COMPOSITE_TEST,""""""1"""""",TEST_CLAUSE,TEST @Value(FYLKE_KODE) = 56",Fylke56
    Fylke16 -> AttributeCreator_11
    Fylke17 -> AttributeCreator_11
    Fylke50 -> Junction
    gamleFylkesnr -> Junction
    Fylke51 -> AttributeCreator_30
    Fylke51 -> AttributeCreator_29
    Fylke52 -> AttributeCreator_28
    Fylke52 -> AttributeCreator_27
    Fylke53 -> AttributeCreator_22
    Fylke53 -> AttributeCreator_21
    Fylke54 -> AttributeCreator_24
    Fylke54 -> AttributeCreator_23
    Fylke55 -> AttributeCreator_17
    Fylke55 -> AttributeCreator_15
    Fylke55 -> AttributeCreator_19
    Fylke55 -> AttributeCreator_20
    Fylke56 -> AttributeCreator_13
    Fylke56 -> AttributeCreator_12
AttributeCreator_11
    ATTR_TABLE = SET_TO FYLKE_KODE = 50
    -> Junction_5
Junction
    -> Junction_5
Junction_5
    -> Junction_5_Output (output)
Junction_5_Output (output)

Bookmark: Vestland
AttributeCreator_30
    ATTR_TABLE = SET_TO FYLKE_KODE = 12
    -> Junction_5
AttributeCreator_29
    ATTR_TABLE = SET_TO FYLKE_KODE = 14
    -> Junction_5

Bookmark: Agder
AttributeCreator_28
    ATTR_TABLE = SET_TO FYLKE_KODE = 9
    -> Junction_5
AttributeCreator_27
    ATTR_TABLE = SET_TO FYLKE_KODE = 10
    -> Junction_5

Bookmark: Vestfold og Telemark
AttributeCreator_22
    ATTR_TABLE = SET_TO FYLKE_KODE = 7
    -> Junction_5
AttributeCreator_21
    ATTR_TABLE = SET_TO FYLKE_KODE = 8
    -> Junction_5

Bookmark: Innlandet
AttributeCreator_24
    ATTR_TABLE = SET_TO FYLKE_KODE = 4
    -> Junction_5
AttributeCreator_23
    ATTR_TABLE = SET_TO FYLKE_KODE = 5
    -> Junction_5

Bookmark: Viken
AttributeCreator_17
    ATTR_TABLE = SET_TO FYLKE_KODE = 1
    -> Junction_5
AttributeCreator_15
    ATTR_TABLE = SET_TO FYLKE_KODE = 2
    -> Junction_5
AttributeCreator_19
    ATTR_TABLE = SET_TO FYLKE_KODE = 5
    -> Junction_5
AttributeCreator_20
    ATTR_TABLE = SET_TO FYLKE_KODE = 6
    -> Junction_5

Bookmark: Troms og Finnmark
AttributeCreator_13
    ATTR_TABLE = SET_TO FYLKE_KODE = 19
    -> Junction_5
AttributeCreator_12
    ATTR_TABLE = SET_TO FYLKE_KODE = 20
    -> Junction_5
